FME workspace CLIPPER2.fmw

Parameters:
- PEMOTONG = ags-sde   # FAMILY:Esri ArcSDE Geodatabase Connection
- IGT = ags-sde   # FAMILY:Esri ArcSDE Geodatabase Connection
- DestDataset_POSTGIS = pgisdb   # Connection

Readers:
- GEODATABASE_SDE_3: GEODATABASE_SDE from $(PEMOTONG)
- GEODATABASE_SDE_2: GEODATABASE_SDE from $(IGT)

Writers:
- POSTGIS_1: POSTGIS to $(DestDataset_POSTGIS)

ADMIN_KABKOTA_2022 (reader GEODATABASE_SDE_3)
    attributes: objectid integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, st_area(shape) double, st_length(shape) double
    -> Tester
Tester
    BOOL_OP = OR
    TEST_CLAUSE = TEST @Value(wadmpr) = Kalimantan Barat
    TEST_MODE = TEST
    PASSED -> AttributeKeeper
AttributeKeeper
    CREATE_BULK_MODE_FEATURES = NO
    KEEP_ATTRS = wadmpr
    -> Clipper [CLIPPER]
PIPPIB_2022_2_AR_250K (reader GEODATABASE_SDE_2)
    attributes: objectid integer, pippib22_2 char(20), namaobj char(50), lcode char(50), fcode char(50), srs_id char(50), metadata char(50), remark char(100), st_area(shape) double, st_length(shape) double
    -> AttributeKeeper_2
AttributeKeeper_2
    CREATE_BULK_MODE_FEATURES = NO
    KEEP_ATTRS = fcode,lcode,metadata,namaobj,pippib22_2,remark,srs_id
    -> Clipper [CANDIDATE]
Clipper
    ADD_NODATA = YES
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    INSIDE -> IGT_LCODE (writer POSTGIS_1)
IGT_LCODE (writer POSTGIS_1)
    attributes: pippib22_2 varchar(20), namaobj varchar(50), lcode varchar(50), fcode varchar(50), srs_id varchar(50), metadata varchar(50), remark varchar(100)
