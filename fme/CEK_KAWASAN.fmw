FME workspace CEK_KAWASAN.fmw
Title: MULTI to GEODATABASE_FILE

Parameters:
- PEMOTONG = AGS-SDE   # Connection
- SourceDataset_FILEGDB_4 = F:\test\PPHKM_AR_50K.gdb   # File Geodatabase
- DestDataset_XLSXW = F:\test\CEK_LUASAN.xlsx   # Destination Microsoft Excel File
- SourceDataset_FFS_3 = $(FME_MF_DIR)KWSHUTAN_AR_250K_072024.ffs   # Source FME Feature Store (FFS) File(s)
- SourceDataset_FFS = $(FME_MF_DIR)FINAL_FIX_KAB_KOT.ffs   # Source FME Feature Store (FFS) File(s)

Readers:
- GEODATABASE_SDE_1: GEODATABASE_SDE from $(PEMOTONG)
- FILEGDB_3: FILEGDB from $(SourceDataset_FILEGDB_4)
- FFS_1: FFS from $(SourceDataset_FFS)
- FFS_2: FFS from $(SourceDataset_FFS_3)

Writers:
- XLSXW_1: XLSXW to $(DestDataset_XLSXW)

FINAL_FIX_KAB_KOT (reader FFS_1)
    attributes: OBJECTID int32, NAMOBJ varchar(250), FCODE varchar(50), REMARK varchar(250), METADATA varchar(50), SRS_ID varchar(50), KDBBPS varchar(50), KDCBPS varchar(50), KDCPUM varchar(50), KDEBPS varchar(50), KDEPUM varchar(50), KDPBPS varchar(50), KDPKAB varchar(50), KDPPUM varchar(50), LUASWH real64, TIPADM int32, WADMKC varchar(50), WADMKD varchar(50), WADMKK varchar(50), WADMPR varchar(50), WIADKC varchar(50), WIADKK varchar(50), WIADPR varchar(50), WIADKD int32, KDBPUM varchar(50), TIPBDR int32, Luas_2021 real64, prst_perub real64, Luas_2022 real64, Selisih_20 real64,
      Luas_2023 real64, Perbedaan_ real64, Catatan_20 varchar(150), Luas real64
    -> Pilih_Provinsi
Pilih_Provinsi: Tester
    BOOL_OP = OR
    TEST_CLAUSE = TEST @Value(WADMPR) = @Value(WADMPR)
    TEST_MODE = TEST
    PASSED -> Pilih_Attribut_Provinsi
Pilih_Attribut_Provinsi: AttributeKeeper
    CREATE_BULK_MODE_FEATURES = NO
    KEEP_ATTRS = WADMPR,KDPPUM
    -> SpatialFilter [Filter]
    -> Clipper [CANDIDATE]
KWSHUTAN_AR_250K_072024 (reader FFS_2)
    attributes: OBJECTID int32, NO_REG int32, KODE_PROV int16, FUNGSIKWS int32, NOSKKWS varchar(100), TGLSKKWS datetime, LSKKWS real64, NAMOBJ varchar(250), FCODE varchar(50), LCODE varchar(8), METADATA varchar(50), SRS_ID varchar(50), REMARK varchar(250)
    -> Pilih_Attribut_IGT
Pilih_Attribut_IGT: AttributeKeeper
    CREATE_BULK_MODE_FEATURES = NO
    KEEP_ATTRS = METADATA,FUNGSIKWS
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDICATES = INTERSECTS
    USE_BOUNDING_BOX = No
    PASSED -> Clipper [CLIPPER]
Clipper
    ADD_NODATA = YES
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    INSIDE -> EsriReprojector
    INSIDE -> GeographicAreaCalculator [off]
GeographicAreaCalculator
    AREA_ATTR = _area
    AreaMult = 0.0001
    -> StatisticsCalculator [off]
EsriReprojector
    DEST = ESRIWKT|World_Cylindrical_Equal_Area|PROJCS["World_Cylindrical_Equal_Area",GEOGCS["GCS_WGS_1984",DATUM["D_WGS_1984",SPHEROID["WGS_1984",6378137.0,298.257223563]],PRIMEM["Greenwich",0.0],UNIT["Degree",0.0174532925199433]],PROJECTION["Cylindrical_Equal_Area"],PARAMETER["False_Easting",0.0],PARAMETER["False_Northing",0.0],PARAMETER["Central_Meridian",0.0],PARAMETER["Standard_Parallel_1",0.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    REPROJECTED -> AreaCalculator
AreaCalculator
    AREA_ATTR = _area
    AREA_TYPE = Plane Area
    MULT = 0.0001
    -> StatisticsCalculator
StatisticsCalculator
    ATTR_ACCUM_MODE = None
    CALCULATION_MODE = NUMERIC
    FEAT_STATS = _area,NUMERIC_MODE,,,,SUM,,,,,,,,,
    GROUP_BY = FUNGSIKWS WADMPR
    SUMMARY -> DatabaseJoiner
DatabaseJoiner
    ADDED_FIELDS = FUNGSI_KWS LABEL_KWS NOURUT_KWS
    ATTR_ACCUM_MODE = Merge Joined
    ATTR_CONFLICT_RES = Use Original
    DATASET = $(FME_MF_DIR_ENCODED)KODE_IGT.xlsx
    FORMAT = XLSXR
    JOIN_KEYS = FUNGSIKWS KD_KWS
    MATCH_MULTIPLE_DISPLAY = Create a feature for each match
    MATCH_RULE_DISPLAY = Match All (1:M)
    TABLE = KAWASAN
    XLSXR_ALLOW_DOLLAR_SIGNS = YES
    XLSXR_APPLY_FILTERS = No
    XLSXR_CASE_SENSITIVE_FEATURE_TYPES = YES
    XLSXR_CONFIGURATION_DATASET = $(FME_MF_DIR)KODE_IGT.xlsx
    XLSXR_CREATE_FEATURE_TABLES_FROM_DATA = Yes
    XLSXR_EXCEL_COL_NAMES = YES
    XLSXR_EXPANDED_DATES_SCANNING = No
    XLSXR_EXPAND_MERGED_CELLS = Yes
    XLSXR_EXPOSED_ATTRS = xlsx_row_id,number(11,0)
    XLSXR_FORCE_DATETIME = NO
    XLSXR_QUERY_FEATURE_TYPES_FOR_MERGE_FILTERS = Yes
    XLSXR_READ_BLANK_AS = Null
    XLSXR_READ_FORM_CONTROLS = NONE
    XLSXR_READ_RASTER_MODE = None
    XLSXR_REPLACE_ONLY_NEWLINES_CARRIAGE_RETURNS = YES
    XLSXR_SCAN_FOR_GEOMETRIC_TYPES = Yes
    XLSXR_SCAN_MAX_FEATURES = 1000
    XLSXR_SCHEMA = KAWASAN,0,KD_KWS,time,,,,1,FUNGSI_KWS,char,43,,,2,LABEL_KWS,char,9,,,3,NOURUT_KWS,number,2,0,,1,,,,NO,NO,1,F:\test\FME_FORM\DataFFS\KODE_IGT.xlsx,"0,0,3,20",PL,NO,NO
    XLSXR_SCHEMA_HANDLING_REVISION = 2
    XLSXR_SKIP_EMPTY_ROWS = YES
    XLSXR_STRIP_SHEETNAME_SPACES = YES
    XLSXR_TABLELIST = KAWASAN
    XLSXR_TRIM_ATTR_NAME_WHITESPACE = Yes
    XLSXR_USE_CUSTOM_SCHEMA = NO
    JOINED -> AttributeRounder
AttributeRounder
    PLACES = 5
    ROUND_TYPE = Nearest
    SRC_ATTRS = _area.sum
    -> Inspector [off]
    -> AttributeManager
Inspector
AttributeManager
    ATTR_TABLE:
      RENAME_SET_VALUE WADMPR > PROVINSI (varchar(50))
      RENAME_SET_VALUE FUNGSI_KWS > KAWASAN (varchar(43))
      RENAME_SET_VALUE _area.sum > LUAS_HA (real64)
      RENAME_SET_VALUE LABEL_KWS > LABEL (varchar(9))
      RENAME_SET_VALUE NOURUT_KWS > NOURUT (int16)
      REMOVE _matched_records (uint32)
    -> KAWASAN (writer XLSXW_1)
KAWASAN (writer XLSXW_1)
    attributes: PROVINSI string(50), KAWASAN auto, LUAS_HA number(20), LABEL auto, FUNGSIKWS number(20), NOURUT auto
