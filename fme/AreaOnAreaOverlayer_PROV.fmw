FME workspace AreaOnAreaOverlayer_PROV.fmw

Parameters:
- SourceDataset_GEODATABASE_FILE = D:\sigap\IGT_KLHK_2022.gdb   # File Geodatabase
- DestDataset_SHAPEFILE_3 = C:\Temp\TEST_FME\TEST_FME.zip   # Destination Esri Shapefile Folder
- DestDataset_SHAPEFILE = C:\Temp\TEST_FME\TEST_FME.zip   # Destination Esri Shapefile Folder

Readers:
- GEODATABASE_FILE_1: GEODATABASE_FILE from $(SourceDataset_GEODATABASE_FILE)

Writers:
- SHAPEFILE_2: SHAPEFILE to $(DestDataset_SHAPEFILE_3)
- SHAPEFILE_1: SHAPEFILE to $(DestDataset_SHAPEFILE)

ADMIN_KABKOTA_2022 (reader GEODATABASE_FILE_1)
    attributes: OBJECTID integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, Shape_Length double, Shape_Area double
    -> Tester
Tester
    BOOL_OP = OR
    TEST_CLAUSE = TEST @Value(wadmpr) = Bali
    TEST_MODE = TEST
    PASSED -> AttributeKeeper
    PASSED -> FeatureReader [INITIATOR]
FeatureReader
    ATTRIBUTES = PL2019R_2020,"OBJECTID,pl2020_id,pl2019_id_r,Shape_Length,Shape_Area"
    ATTR_ACCUM_MODE = Only Use Result
    COMBINE_GEOM = Use Result
    DATASET = D:\upload\GDB\PL2019R_2020.gdb
    FEATURETYPES = PL2019R_2020
    FORMAT = GEODATABASE_FILE
    GEODATABASE_FILE_ALIAS_MODE = NONE
    GEODATABASE_FILE_CACHE_MULTIPATCH_TEXTURES = yes
    GEODATABASE_FILE_CHECK_SIMPLE_GEOM = no
    GEODATABASE_FILE_CREATE_FEATURE_TABLES_FROM_DATA = Yes
    GEODATABASE_FILE_FEATURE_READ_MODE = Features
    GEODATABASE_FILE_IGNORE_NETWORK_INFO = yes
    GEODATABASE_FILE_IGNORE_RELATIONSHIP_INFO = yes
    GEODATABASE_FILE_MERGE_FEAT_LINKED_ANNOS = no
    GEODATABASE_FILE_QUERY_FEATURE_TYPES_FOR_MERGE_FILTERS = Yes
    GEODATABASE_FILE_READ_THREE_POINT_ARCS = no
    GEODATABASE_FILE_RESOLVE_DOMAINS = no
    GEODATABASE_FILE_RESOLVE_SUBTYPE_NAMES = yes
    GEODATABASE_FILE_SIMPLE_DONUT_GEOMETRY = no
    GEODATABASE_FILE_SPLIT_COMPLEX_ANNOS = no
    GEODATABASE_FILE_SPLIT_COMPLEX_EDGES = no
    GEODATABASE_FILE_SPLIT_MULTI_PART_ANNOS = no
    GEODATABASE_FILE_STRIP_GUID_GLOBALID_BRACES = no
    GEODATABASE_FILE_TABLELIST = WAD_KABKOTA
    GEODATABASE_FILE_TRANSLATE_SPATIAL_DATA_ONLY = no
    GEODATABASE_FILE_USE_SEARCH_ENVELOPE = NO
    INTERACT = ENVELOPE_INTERSECTS
    ORDER_RESULTS = No
    OUTPUT_FEATURES_DISPLAY = Schema and Data Features
    PL2019R_2020 -> AttributeKeeper_2
AttributeKeeper_2
    CREATE_BULK_MODE_FEATURES = NO
    KEEP_ATTRS = pl2019_id_r,pl2020_id
    -> AreaOnAreaOverlayer [AREA]
AttributeKeeper
    CREATE_BULK_MODE_FEATURES = NO
    KEEP_ATTRS = wadmkk,wadmpr
    -> AreaOnAreaOverlayer [AREA]
AreaOnAreaOverlayer
    ACCUM_ATTRS_NAME = Merge Incoming Attributes
    CLEANING_TOLERANCE = Automatic
    CONNECT_Z_MODE = First Wins
    DEAGGREGATE_INPUT = Yes
    OVC_ATTR = _overlaps
    AREA -> Tester_2
Tester_2
    BOOL_OP = OR
    TEST_CLAUSE = TEST @Value(_overlaps) = 2
    TEST_MODE = TEST
    PASSED -> AttributeKeeper_3
AttributeKeeper_3
    CREATE_BULK_MODE_FEATURES = NO
    KEEP_ATTRS = pl2019_id_r,wadmkk,wadmpr,pl2020_id
    -> ADMIN_KABKOTA_2022 (writer SHAPEFILE_1)
ADMIN_KABKOTA_2022 (writer SHAPEFILE_1)
    attributes: OBJECTID long, namobj varchar(250), fcode varchar(50), remark varchar(250), metadata varchar(50), srs_id varchar(50), kdbbps varchar(50), kdcbps varchar(50), kdcpum varchar(50), kdebps varchar(50), kdepum varchar(50), kdpbps varchar(50), kdpkab varchar(50), kdppum varchar(50), luaswh double, tipadm long, wadmkc varchar(50), wadmkd varchar(50), wadmkk varchar(50), wadmpr varchar(50), wiadkc varchar(50), wiadkk varchar(50), wiadpr varchar(50), wiadkd long, Shape_Leng double, Shape_Area double
Inspector
