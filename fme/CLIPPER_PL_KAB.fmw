FME workspace CLIPPER_PL_KAB.fmw
Title: MULTI to GEODATABASE_FILE

Parameters:
- PEMOTONG = ags-sde   # Connection
- OUTPUT = db-klhk   # Connection
- DestDataset_GEODATABASE_FILE = AGS-SDE   # Connection

Readers:
- GEODATABASE_SDE_1: GEODATABASE_SDE from $(PEMOTONG)
- GEODATABASE_SDE_2: GEODATABASE_SDE from $(OUTPUT)

Writers:
- GEODATABASE_SDE_3: GEODATABASE_SDE to $(DestDataset_GEODATABASE_FILE)

PL2022_AR_250K (reader GEODATABASE_SDE_2)
    attributes: objectid integer, kode_prov smallint, pl2021_id_r integer, pl2022_id integer, luas_ha double, ket char(50), namaobj char(50), remark char(100), lcode char(50), fcode char(50), srs_id char(50), metadata char(50), st_area(shape) double, st_length(shape) double
    -> Pilih_Attribut_IGT
Pilih_Attribut_IGT: AttributeKeeper
    CREATE_BULK_MODE_FEATURES = NO
    KEEP_ATTRS = pl2022_id,fcode,ket,lcode,metadata,namaobj,remark,srs_id
    -> SpatialFilter [Candidate]
ADMIN_KABKOTA_2022 (reader GEODATABASE_SDE_1)
    attributes: objectid integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, st_area(shape) double, st_length(shape) double
    -> Pilih_Provinsi
Pilih_Provinsi: Tester
    BOOL_OP = COMPOSITE
    COMPOSITE_TEST = 1 AND 2
    TEST_CLAUSE:
      TEST @Value(wadmpr) = Daerah Istimewa Yogyakarta
      TEST @Value(wadmkk) = Sleman
    TEST_MODE = TEST
    PASSED -> Pilih_Attribut_Provinsi
Pilih_Attribut_Provinsi: AttributeKeeper
    CREATE_BULK_MODE_FEATURES = NO
    KEEP_ATTRS = wadmpr,wadmkk
    -> SpatialFilter [Filter]
    -> Clipper [CANDIDATE]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDICATES = INTERSECTS
    USE_BOUNDING_BOX = No
    PASSED -> Clipper [CLIPPER]
Clipper
    ADD_NODATA = YES
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    INSIDE -> EsriReprojector
    INSIDE -> GeographicAreaCalculator [off]
    INSIDE -> PL_2021_JUNI2022 (writer GEODATABASE_SDE_3) [off]
PL_2021_JUNI2022 (writer GEODATABASE_SDE_3)
    attributes: wadmkk char(50), wadmpr char(50), pl2022_id integer, ket char(50), namaobj char(50), remark char(100), lcode char(50), fcode char(50), srs_id char(50), metadata char(50)
GeographicAreaCalculator
    AREA_ATTR = _area
    AreaMult = 0.0001
    -> StatisticsCalculator [off]
EsriReprojector
    DEST = ESRIWKT|World_Cylindrical_Equal_Area|PROJCS["World_Cylindrical_Equal_Area",GEOGCS["GCS_WGS_1984",DATUM["D_WGS_1984",SPHEROID["WGS_1984",6378137.0,298.257223563]],PRIMEM["Greenwich",0.0],UNIT["Degree",0.0174532925199433]],PROJECTION["Cylindrical_Equal_Area"],PARAMETER["False_Easting",0.0],PARAMETER["False_Northing",0.0],PARAMETER["Central_Meridian",0.0],PARAMETER["Standard_Parallel_1",0.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    REPROJECTED -> AreaCalculator
AreaCalculator
    AREA_ATTR = _area
    AREA_TYPE = Plane Area
    MULT = 0.0001
    -> StatisticsCalculator
StatisticsCalculator
    CALCULATION_MODE = NUMERIC
    FEAT_STATS = _area,NUMERIC_MODE,,,,SUM,,,,,,,,,
    GROUP_BY = pl2022_id wadmkk wadmpr
    SUMMARY -> AttributeRounder
AttributeRounder
    PLACES = 3
    ROUND_TYPE = Nearest
    SRC_ATTRS = _area.sum
    -> DatabaseJoiner
DatabaseJoiner
    ADDED_FIELDS = kelas_pl
    ATTR_ACCUM_MODE = Merge Joined
    ATTR_CONFLICT_RES = Use Original
    CACHE_SIZE = 5000
    DATASET = AGS-SDE
    FORMAT = GEODATABASE_SDE
    GEODATABASE_SDE_CREATE_FEATURE_TABLES_FROM_DATA = Yes
    GEODATABASE_SDE_NAMED_CONNECTION = AGS-SDE
    GEODATABASE_SDE_QUERY_FEATURE_TYPES_FOR_MERGE_FILTERS = Yes
    GEODATABASE_SDE_REMOVE_TABLE_QUALIFIER = NO
    JOIN_KEYS = pl2022_id kode_pl
    MATCH_MULTIPLE_DISPLAY = Create a feature for each match
    MATCH_RULE_DISPLAY = Match All (1:M)
    PREFETCH_EXHAUSTIVE = Yes
    TABLE = sde.DMN_PL
    JOINED -> AttributeRenamer
AttributeRenamer
    ATTR_TABLE:
      RENAME_SET_DEFAULT wadmkk > Kab_Kota
      RENAME_SET_DEFAULT wadmpr > Provinsi
      RENAME_SET_DEFAULT _area.sum > Luas_Ha
      RENAME_SET_DEFAULT pl2022_id > Kode_PL
      RENAME_SET_DEFAULT kelas_pl > Keterangan
    MISSING_INPUT_ATTRS = REMOVE
    -> AttributeRemover
AttributeRemover
    REMOVE_ATTRS = _matched_records
    -> Inspector
Inspector
