FME workspace EXCEL_TO_GDB.fmw

Parameters:
- SourceDataset_XLSXR = D:\Rapat\Sahira\KAMUSDATA\LIST IGT.xlsx   # Source Microsoft Excel File(s)
- SourceDataset_XLSXR_3 = D:\Rapat\Sahira\KAMUSDATA\LIST IGT.xlsx   # Source Microsoft Excel File(s)
- DestDataset_GEODATABASE_SDE = ags-sde   # ArcSDE Geodatabase Connection

Readers:
- XLSXR_1: XLSXR from $(SourceDataset_XLSXR)
- XLSXR_2: XLSXR from $(SourceDataset_XLSXR_3)

Writers:
- GEODATABASE_SDE_1: GEODATABASE_SDE to $(DestDataset_GEODATABASE_SDE)

LIST_IGT (reader XLSXR_1)
    attributes: NO_IGT number(3,0), PRODUSEN char(90), BIDANG char(1), KODE_BIDANG number(1,0), IGT_NO number(2,0), SCODE number(1,0), TYPE char(2), LCODE char(7), NAMA_IGT char(164), NAMA_ALIAS_IGT char(51), Skala char(23)
    -> FeatureJoiner [LEFT]
ID_BIDANG (reader XLSXR_2)
    attributes: ID_BIDANG number(2,0), KODE_BIDANG char(1), BIDANG char(7), BIDANG_TEMATIK char(58)
    -> FeatureJoiner [RIGHT]
FeatureJoiner
    ATTR_CONFLICT_RES = Prefer Left
    GEOMETRY_HANDLING = Prefer Left
    JOIN_KEYS = KODE_BIDANG ID_BIDANG AUTO
    JOIN_MODE = Inner
    JOINED -> LIST_IGT_BIDANG (writer GEODATABASE_SDE_1)
LIST_IGT_BIDANG (writer GEODATABASE_SDE_1)
    attributes: NO_IGT smallint, PRODUSEN char(90), BIDANG char(1), KODE_BIDANG smallint, IGT_NO smallint, SCODE smallint, TYPE char(2), LCODE char(7), NAMA_IGT char(164), NAMA_ALIAS_IGT char(51), Skala char(23)
