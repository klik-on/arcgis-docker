FME workspace CLIPPER.fmw

Parameters:
- PEMOTONG = ags-sde   # FAMILY:Esri ArcSDE Geodatabase Connection
- IGT = ags-sde   # FAMILY:Esri ArcSDE Geodatabase Connection
- OUTPUT = ags-sde   # FAMILY:Esri ArcSDE Geodatabase Connection

Readers:
- GEODATABASE_SDE_1: GEODATABASE_SDE from $(PEMOTONG)
- GEODATABASE_SDE_4: GEODATABASE_SDE from $(OUTPUT)

Writers:
- POSTGIS_1: POSTGIS to $(IGT) in EPSG4326

ADMIN_KABKOTA_2022 (reader GEODATABASE_SDE_1)
    attributes: objectid integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, st_area(shape) double, st_length(shape) double
    -> Pilih_Provinsi
Pilih_Provinsi: Tester
    BOOL_OP = OR
    TEST_CLAUSE = TEST @Value(wadmpr) = Lampung
    TEST_MODE = TEST
    PASSED -> Pilih_Attribut_Provinsi
Pilih_Attribut_Provinsi: AttributeKeeper
    CREATE_BULK_MODE_FEATURES = NO
    KEEP_ATTRS = wadmpr
    -> Clipper [CLIPPER]
PIPPIB_2022_2_AR_250K (reader GEODATABASE_SDE_4)
    attributes: objectid integer, pippib22_2 char(20), namaobj char(50), lcode char(50), fcode char(50), srs_id char(50), metadata char(50), remark char(100), st_area(shape) double, st_length(shape) double
    -> Pilih_Attribut_IGT
Pilih_Attribut_IGT: AttributeKeeper
    CREATE_BULK_MODE_FEATURES = NO
    KEEP_ATTRS = pippib22_2
    -> Clipper [CANDIDATE]
Clipper
    ADD_NODATA = YES
    BOUNDARY_CASES = INSIDE
    CLEANING_TOLERANCE = Automatic
    CLIPPED_ATTR = _clipped
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_INTERIM
    PRESERVE_RASTER_EXTENTS = NO
    RASTER_CELL_MODE = CENTER
    Z_VAL_SOURCE = CANDIDATE
    INSIDE -> IGT_CLIP_LAMPUNG (writer POSTGIS_1)
IGT_CLIP_LAMPUNG (writer POSTGIS_1)
    attributes: pippib22_2 varchar(20), _clipped varchar(3)
Inspector
