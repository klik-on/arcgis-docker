FME workspace TEST-POTONG.fmw

Parameters:
- PEMOTONG = D:\sigap\IGT_KLHK_2022.gdb   # File Geodatabase
- IGT = ags-sde   # FAMILY:Esri ArcSDE Geodatabase Connection
- OUTPUT = D:\sigap\PL2021_JUN2022\PL_2021_JUNI2022.gdb   # File Geodatabase

Readers:
- GEODATABASE_FILE_1: GEODATABASE_FILE from $(PEMOTONG)
- GEODATABASE_FILE_2: GEODATABASE_FILE from $(OUTPUT)

Writers:
- POSTGIS_1: POSTGIS to $(IGT) in EPSG4326

ADMIN_KABKOTA_2022 (reader GEODATABASE_FILE_1)
    attributes: OBJECTID integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, Shape_Length double, Shape_Area double
    -> Pilih_Provinsi
Pilih_Provinsi: Tester
    BOOL_OP = OR
    TEST_CLAUSE = TEST @Value(wadmpr) = Bali
    TEST_MODE = TEST
    PASSED -> Pilih_Attribut_Provinsi
Pilih_Attribut_Provinsi: AttributeKeeper
    CREATE_BULK_MODE_FEATURES = NO
    KEEP_ATTRS = wadmpr
    -> SpatialFilter [Filter]
PL_2021_JUNI2022 (reader GEODATABASE_FILE_2)
    attributes: OBJECTID integer, KODE_PROV smallint, PL2021_ID integer, LUAS_HA double, PL2020_ID_R integer, Shape_Length double, Shape_Area double
    -> Pilih_Attribut_IGT
Pilih_Attribut_IGT: AttributeKeeper
    CREATE_BULK_MODE_FEATURES = NO
    KEEP_ATTRS = PL2021_ID
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> Inspector
Inspector
IGT_CLIP_LAMPUNG (writer POSTGIS_1)
