FME workspace CLIPPER-PROV.fmw
Title: MULTI to GEODATABASE_FILE

Parameters:
- PEMOTONG = $(FME_MF_DIR)gdb_fme.gdb   # File Geodatabase
- DestDataset_GEODATABASE_FILE = $(FME_MF_DIR)fme_out.gdb   # File Geodatabase
- OUTPUT = $(FME_MF_DIR)gdb_fme.gdb   # File Geodatabase
- DestDataset_GEODATABASE_FILE_4 = $(FME_MF_DIR)fme_out.gdb   # File Geodatabase

Readers:
- GEODATABASE_FILE_1: GEODATABASE_FILE from $(PEMOTONG)
- GEODATABASE_FILE_4: GEODATABASE_FILE from $(OUTPUT)

Writers:
- GEODATABASE_FILE_3: GEODATABASE_FILE to $(DestDataset_GEODATABASE_FILE)
- GEODATABASE_FILE_2: GEODATABASE_FILE to $(DestDataset_GEODATABASE_FILE_4)

ADMIN_KABKOTA_2022 (reader GEODATABASE_FILE_1)
    attributes: OBJECTID integer, namobj char(250), fcode char(50), remark char(250), metadata char(50), srs_id char(50), kdbbps char(50), kdcbps char(50), kdcpum char(50), kdebps char(50), kdepum char(50), kdpbps char(50), kdpkab char(50), kdppum char(50), luaswh double, tipadm integer, wadmkc char(50), wadmkd char(50), wadmkk char(50), wadmpr char(50), wiadkc char(50), wiadkk char(50), wiadpr char(50), wiadkd integer, SHAPE_Length double, SHAPE_Area double
    -> TestFilter_KALIMANTAN
    -> TestFilter_SUMATERA
    -> TestFilter_SULAWESI
    -> TestFilter_MALUKU
    -> TestFilter_PAPUA
    -> TestFilter_JAWA
    -> TestFilter_BALINUSA
TestFilter_SUMATERA
    DEFAULT_VALUE = <UNFILTERED>
    PASSED_TEST_GROUP_OUTPUT = FIRST
    TEST_LIST = "BOOL_OP,OR,COMPOSITE_TEST,""""""1"""""",TEST_CLAUSE,TEST @Value(wadmpr) = Aceh",Aceh,"BOOL_OP,OR,COMPOSITE_TEST,""""""1"""""",TEST_CLAUSE,TEST @Value(wadmpr) = Bengkulu",Bengkulu,"BOOL_OP,OR,COMPOSITE_TEST,""""""1"""""",TEST_CLAUSE,TEST @Value(wadmpr) = Jambi",Jambi,"BOOL_OP,OR,COMPOSITE_TEST,""""""1"""""",TEST_CLAUSE,TEST @Value(wadmpr) = Kepulauan Bangka Belitung",Kepulauan Bangka Belitung,"BOOL_OP,OR,COMPOSITE_TEST,""""""1"""""",TEST_CLAUSE,TEST @Value(wadmpr) = Kepulauan Riau",Kepulauan Riau,"BOOL_OP,OR,COMPOSITE_TEST,""""""1"""""",TEST_CLAUSE,TEST @Value(wadmpr) = Lampung",Lampung,"BOOL_OP,OR,COMPOSITE_TEST,""""""1"""""",TEST_CLAUSE,TEST @Value(wadmpr) = Riau",Riau,"BOOL_OP,OR,COMPOSITE_TEST,""""""1"""""",TEST_CLAUSE,TEST @Value(wadmpr) = Sumatera Barat",Sumatera Barat,"BOOL_OP,OR,COMPOSITE_TEST,""""""1"""""",TEST_CLAUSE,TEST @Value(wadmpr) = Sumatera Selatan",Sumatera Selatan,"BOOL_OP,OR,COMPOSITE_TEST,""""""1"""""",TEST_CLAUSE,TEST @Value(wadmpr) = Sumatera Utara",Sumatera Utara
    Aceh -> Attribut_SUMATERA
    Bengkulu -> Attribut_SUMATERA
    Kepulauan Riau -> Attribut_SUMATERA
    Lampung -> Attribut_SUMATERA
    Jambi -> Attribut_SUMATERA
    Riau -> Attribut_SUMATERA
    Sumatera Barat -> Attribut_SUMATERA
    Sumatera Selatan -> Attribut_SUMATERA
    Sumatera Utara -> Attribut_SUMATERA
    Kepulauan Bangka Belitung -> Attribut_SUMATERA
Attribut_SUMATERA: AttributeKeeper
    CREATE_BULK_MODE_FEATURES = NO
    KEEP_ATTRS = wadmpr,wadmkk
    -> Clipper [CANDIDATE]
    -> SpatialFilter [Filter]
TestFilter_KALIMANTAN
    DEFAULT_VALUE = <UNFILTERED>
    PASSED_TEST_GROUP_OUTPUT = FIRST
    TEST_LIST = "BOOL_OP,OR,COMPOSITE_TEST,""""""1"""""",TEST_CLAUSE,TEST @Value(wadmpr) = Kalimantan Barat",Kalimantan Barat,"BOOL_OP,OR,COMPOSITE_TEST,""""""1"""""",TEST_CLAUSE,TEST @Value(wadmpr) = Kalimantan Selatan",Kalimantan Selatan,"BOOL_OP,OR,COMPOSITE_TEST,""""""1"""""",TEST_CLAUSE,TEST @Value(wadmpr) = Kalimantan Tengah",Kalimantan Tengah,"BOOL_OP,OR,COMPOSITE_TEST,""""""1"""""",TEST_CLAUSE,TEST @Value(wadmpr) = Kalimantan Timur",Kalimantan Timur,"BOOL_OP,OR,COMPOSITE_TEST,""""""1"""""",TEST_CLAUSE,TEST @Value(wadmpr) = Kalimantan Utara",Kalimantan Utara
    Kalimantan Barat -> Attribut_KALIMANTAN
    Kalimantan Selatan -> Attribut_KALIMANTAN
    Kalimantan Tengah -> Attribut_KALIMANTAN
    Kalimantan Utara -> Attribut_KALIMANTAN
    Kalimantan Timur -> Attribut_KALIMANTAN
Attribut_KALIMANTAN: AttributeKeeper
    CREATE_BULK_MODE_FEATURES = NO
    KEEP_ATTRS = wadmpr,wadmkk
    -> Clipper [CANDIDATE]
    -> SpatialFilter [Filter]
TestFilter_SULAWESI
    DEFAULT_VALUE = <UNFILTERED>
    PASSED_TEST_GROUP_OUTPUT = FIRST
    TEST_LIST = "BOOL_OP,OR,COMPOSITE_TEST,""""""1"""""",TEST_CLAUSE,TEST @Value(wadmpr) = Gorontalo",Gorontalo,"BOOL_OP,OR,COMPOSITE_TEST,""""""1"""""",TEST_CLAUSE,TEST @Value(wadmpr) = Sulawesi Barat",Sulawesi Barat,"BOOL_OP,OR,COMPOSITE_TEST,""""""1"""""",TEST_CLAUSE,TEST @Value(wadmpr) = Sulawesi Selatan",Sulawesi Selatan,"BOOL_OP,OR,COMPOSITE_TEST,""""""1"""""",TEST_CLAUSE,TEST @Value(wadmpr) = Sulawesi Tengah",Sulawesi Tengah,"BOOL_OP,OR,COMPOSITE_TEST,""""""1"""""",TEST_CLAUSE,TEST @Value(wadmpr) = Sulawesi Tenggara",Sulawesi Tenggara,"BOOL_OP,OR,COMPOSITE_TEST,""""""1"""""",TEST_CLAUSE,TEST @Value(wadmpr) = Sulawesi Utara",Sulawesi Utara
    Gorontalo -> Attribut_SULAWESI
    Sulawesi Barat -> Attribut_SULAWESI
    Sulawesi Selatan -> Attribut_SULAWESI
    Sulawesi Tengah -> Attribut_SULAWESI
    Sulawesi Tenggara -> Attribut_SULAWESI
    Sulawesi Utara -> Attribut_SULAWESI
Attribut_SULAWESI: AttributeKeeper
    CREATE_BULK_MODE_FEATURES = NO
    KEEP_ATTRS = wadmpr,wadmkk
    -> Clipper [CANDIDATE]
    -> SpatialFilter [Filter]
TestFilter_MALUKU
    DEFAULT_VALUE = <UNFILTERED>
    PASSED_TEST_GROUP_OUTPUT = FIRST
    TEST_LIST = "BOOL_OP,OR,COMPOSITE_TEST,""""""1"""""",TEST_CLAUSE,TEST @Value(wadmpr) = Maluku",Maluku,"BOOL_OP,OR,COMPOSITE_TEST,""""""1"""""",TEST_CLAUSE,TEST @Value(wadmpr) = Maluku Utara",Maluku Utara
    Maluku -> Attribut_MALUKU
    Maluku Utara -> Attribut_MALUKU
Attribut_MALUKU: AttributeKeeper
    CREATE_BULK_MODE_FEATURES = NO
    KEEP_ATTRS = wadmpr,wadmkk
    -> Clipper [CANDIDATE]
    -> SpatialFilter [Filter]
TestFilter_PAPUA
    DEFAULT_VALUE = <UNFILTERED>
    PASSED_TEST_GROUP_OUTPUT = FIRST
    TEST_LIST = "BOOL_OP,OR,COMPOSITE_TEST,""""""1"""""",TEST_CLAUSE,TEST @Value(wadmpr) = Papua",Papua,"BOOL_OP,OR,COMPOSITE_TEST,""""""1"""""",TEST_CLAUSE,TEST @Value(wadmpr) = Papua Barat",Papua Barat,"BOOL_OP,OR,COMPOSITE_TEST,""""""1"""""",TEST_CLAUSE,TEST @Value(wadmpr) = Papua Pegunungan",Papua Pegunungan,"BOOL_OP,OR,COMPOSITE_TEST,""""""1"""""",TEST_CLAUSE,TEST @Value(wadmpr) = Papua Selatan",Papua Selatan,"BOOL_OP,OR,COMPOSITE_TEST,""""""1"""""",TEST_CLAUSE,TEST @Value(wadmpr) = Papua Tengah",Papua Tengah
    Papua -> Attribut_PAPUA
    Papua Barat -> Attribut_PAPUA
    Papua Pegunungan -> Attribut_PAPUA
    Papua Selatan -> Attribut_PAPUA
    Papua Tengah -> Attribut_PAPUA
Attribut_PAPUA: AttributeKeeper
    CREATE_BULK_MODE_FEATURES = NO
    KEEP_ATTRS = wadmpr,wadmkk
    -> Clipper [CANDIDATE]
    -> SpatialFilter [Filter]
TestFilter_JAWA
    DEFAULT_VALUE = <UNFILTERED>
    PASSED_TEST_GROUP_OUTPUT = FIRST
    TEST_LIST = "BOOL_OP,OR,COMPOSITE_TEST,""""""1"""""",TEST_CLAUSE,TEST @Value(wadmpr) = DKI Jakarta",DKI Jakarta,"BOOL_OP,OR,COMPOSITE_TEST,""""""1"""""",TEST_CLAUSE,TEST @Value(wadmpr) = Daerah Istimewa Yogyakarta",Daerah Istimewa Yogyakarta,"BOOL_OP,OR,COMPOSITE_TEST,""""""1"""""",TEST_CLAUSE,TEST @Value(wadmpr) = Jawa Barat",Jawa Barat,"BOOL_OP,OR,COMPOSITE_TEST,""""""1"""""",TEST_CLAUSE,TEST @Value(wadmpr) = Jawa Tengah",Jawa Tengah,"BOOL_OP,OR,COMPOSITE_TEST,""""""1"""""",TEST_CLAUSE,TEST @Value(wadmpr) = Jawa Timur",Jawa Timur
    DKI Jakarta -> Attribut_JAWA
    Daerah Istimewa Yogyakarta -> Attribut_JAWA
    Jawa Barat -> Attribut_JAWA
    Jawa Tengah -> Attribut_JAWA
    Jawa Timur -> Attribut_JAWA
Attribut_JAWA: AttributeKeeper
    CREATE_BULK_MODE_FEATURES = NO
    KEEP_ATTRS = wadmpr,wadmkk
    -> Clipper [CANDIDATE]
    -> SpatialFilter [Filter]
TestFilter_BALINUSA
    DEFAULT_VALUE = <UNFILTERED>
    PASSED_TEST_GROUP_OUTPUT = FIRST
    TEST_LIST = "BOOL_OP,OR,COMPOSITE_TEST,""""""1"""""",TEST_CLAUSE,TEST @Value(wadmpr) = Bali",Bali,"BOOL_OP,OR,COMPOSITE_TEST,""""""1"""""",TEST_CLAUSE,TEST @Value(wadmpr) = Nusa Tenggara Barat",Nusa Tenggara Barat,"BOOL_OP,OR,COMPOSITE_TEST,""""""1"""""",TEST_CLAUSE,TEST @Value(wadmpr) = Nusa Tenggara Timur",Nusa Tenggara Timur
    Bali -> Attribut_BALINUSA
    Nusa Tenggara Barat -> Attribut_BALINUSA
    Nusa Tenggara Timur -> Attribut_BALINUSA
Attribut_BALINUSA: AttributeKeeper
    CREATE_BULK_MODE_FEATURES = NO
    KEEP_ATTRS = wadmpr,wadmkk
    -> SpatialFilter [Filter]
    -> Clipper [CANDIDATE]
pktl_ppkh_PLSKWSHUTAN_AR_50K_042023 (reader GEODATABASE_FILE_4)
    attributes: OBJECTID integer, fcode char(50), metadata char(50), srs_id char(50), namobj char(250), remark char(255), kode_prov smallint, nama char(100), noskpls char(100), tglskpls date, lskpls double, jnspls char(50), komoditas char(100), wadmkk char(50), wadmpr char(50), cekcek double, SHAPE_Length double, SHAPE_Area double
    -> Pilih_Attribut_IGT
Pilih_Attribut_IGT: AttributeKeeper
    CREATE_BULK_MODE_FEATURES = NO
    KEEP_ATTRS = OBJECTID,fcode,metadata,srs_id,namobj,remark,kode_prov,SHAPE_Length,SHAPE_Area,nama,noskpls,tglskpls,lskpls,jnspls,komoditas,wadmkk,wadmpr,cekcek
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDICATES = INTERSECTS
    USE_BOUNDING_BOX = No
    PASSED -> Clipper [CLIPPER]
Clipper
    ADD_NODATA = YES
    ATTR_ACCUM_MODE = MERGE
    ATTR_CONFLICT_RES = CANDIDATE
    BOUNDARY_CASES = INSIDE
    CLEANING_TOLERANCE = Automatic
    CLIPPERS_FIRST = NO
    GENERATE_LIST = NO
    INVALID_PARTS_HANDLING = REJECT_WHOLE
    MISSING_M_MODE = Linear Interpolation
    MISSING_Z_MODE = Planar Interpolation
    MULTIPLE_CLIPPERS = YES
    M_VAL_SOURCE = CANDIDATE
    OVERLAPPING_CLIPPERS = CLIP_ORIGINAL
    PRESERVE_RASTER_EXTENTS = NO
    RASTER_CELL_MODE = CENTER
    Z_VAL_SOURCE = CANDIDATE
    INSIDE -> PL__PL_2021_JUNI2022 (writer GEODATABASE_FILE_3)
    INSIDE -> EsriReprojector
PL__PL_2021_JUNI2022 (writer GEODATABASE_FILE_3)
    attributes: wadmkk char(50), wadmpr char(50), OBJECTID integer, fcode char(50), metadata char(50), srs_id char(50), namobj char(250), remark char(255), kode_prov smallint, nama char(100), noskpls char(100), tglskpls date, lskpls double, jnspls char(50), komoditas char(100), cekcek double, SHAPE_Length double, SHAPE_Area double
EsriReprojector
    DEST = ESRIWKT|World_Cylindrical_Equal_Area|PROJCS["World_Cylindrical_Equal_Area",GEOGCS["GCS_WGS_1984",DATUM["D_WGS_1984",SPHEROID["WGS_1984",6378137.0,298.257223563]],PRIMEM["Greenwich",0.0],UNIT["Degree",0.0174532925199433]],PROJECTION["Cylindrical_Equal_Area"],PARAMETER["False_Easting",0.0],PARAMETER["False_Northing",0.0],PARAMETER["Central_Meridian",0.0],PARAMETER["Standard_Parallel_1",0.0],UNIT["Meter",1.0]]
    GEOTRANSFORMATION_NAME = <None>
    INTERPOLATION_TYPE_NAME = Nearest Neighbor
    RASTER_CELL_SIZE = Preserve Cells
    RASTER_TOLERANCE = 0.0
    SOURCE = ESRIWKT|GCS_WGS_1984|GEOGCS["GCS_WGS_1984",DATUM["D_WGS_1984",SPHEROID["WGS_1984",6378137.0,298.257223563]],PRIMEM["Greenwich",0.0],UNIT["Degree",0.0174532925199433]]
    REPROJECTED -> AreaCalculator
AreaCalculator
    AREA_ATTR = _area
    AREA_TYPE = Plane Area
    MULT = 0.0001
    -> StatisticsCalculator
StatisticsCalculator
    CALCULATION_MODE = NUMERIC
    FEAT_STATS = _area,NUMERIC_MODE,,,,SUM,,,,,,,,,
    GROUP_BY = wadmpr jnspls komoditas wadmkk
    SUMMARY -> AttributeRounder
AttributeRounder
    PLACES = 3
    ROUND_TYPE = Nearest
    SRC_ATTRS = _area.sum
    -> AttributeRenamer
AttributeRenamer
    ATTR_TABLE:
      RENAME_SET_DEFAULT wadmpr > Provinsi
      RENAME_SET_DEFAULT _area.sum > Luas_Ha
      RENAME_SET_DEFAULT jnspls > Jenis
      RENAME_SET_DEFAULT komoditas > Komoditas
    MISSING_INPUT_ATTRS = REMOVE
    -> AttributeRemover
AttributeRemover
    REMOVE_ATTRS = _matched_records
    -> FeatureClass1 (writer GEODATABASE_FILE_2)
FeatureClass1 (writer GEODATABASE_FILE_2)
    attributes: Provinsi char(50), Luas_Ha double, Jenis char(50), Komoditas char(100), wadmkk char(50)
