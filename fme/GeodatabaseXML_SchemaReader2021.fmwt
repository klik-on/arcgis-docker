FME workspace GeodatabaseXML_SchemaReader2021.fmwt
Title: Geodatabase XML Schema Reader
Description: Geodatabase XML Schema Reader
Version: 1.0
Version required: FME 2013 or above
Last modified: Feb. 14, 2013
By: Dean at Safe
Purpose: Read all possible schema elements 
from an ESRI Geodatabase XML Workspace Dataset
Uses the Schema reader to get basic table and 
field information.
Uses the XML reader with feature paths to get 
detailed schema information at the
dataset, feature class and field levels 
Also retrieves all dataset metadata.

Parameters:
- DestDataset_XLSXW =
- SourceDataset_XML =

Readers:
- XML_1: XML from $(SourceDataset_XML)

Writers:
- XLSXW_1: XLSXW to $(DestDataset_XLSXW)

Bookmark: Dataset Domains Subtypes and Metadata
Domain (reader XML_1)
    attributes: CodedValues.CodedValue{}.Code xml_char(10), CodedValues.CodedValue{}.Code.type xml_char(10), CodedValues.CodedValue{}.Name xml_char(26), CodedValues.CodedValue{}.type xml_char(16), CodedValues.type xml_char(23), Description xml_char(42), Domain.type xml_char(22), DomainName xml_char(34), Domains.type xml_char(19), Field.type xml_char(11), FieldType xml_char(26), MergePolicy xml_char(20), Owner xml_char(1), SplitPolicy xml_char(20), xml_fragment xml_xml, xml_id xml_char(34), xml_matched_element xml_char(7), xml_parent_child_pos xml_decimal(2,0), xml_parent_id xml_char(28), MaxValue xml_decimal(3,0), MaxValue.type xml_char(10), MinValue xml_decimal(2,0), MinValue.type xml_char(10)
    -> ListExploder_2
ListExploder_2
    ATTR_ACCUM_MODE = Merge List Attributes
    ATTR_CONFLICT_RES = Use List Attribute Values
    INDEX_ATTR = _element_index
    LIST_ATTR = CodedValues.CodedValue{}
    ELEMENTS -> AttributeKeeper_2
AttributeKeeper_2
    CREATE_BULK_MODE_FEATURES = No
    KEEP_ATTRS = Code,DomainName,Name,Code.type,Description,type,Owner
    -> DuplicateFilter
DuplicateFilter
    INPUT_ORDERED_CHOICE = No
    KEYATTR = DomainName Name
    UNIQUE -> DomainCodes (writer XLSXW_1)
DomainCodes (writer XLSXW_1)
    attributes: DomainName string(35), Code auto(20), Name auto(20), Code.type auto(20), Description string(42), type auto(20), Owner string(10)
Subtype (reader XML_1)
    attributes: FieldInfos.type xml_char(29), Subtype.type xml_char(13), SubtypeCode xml_decimal(3,0), SubtypeName xml_char(24), Subtypes.type xml_char(20), xml_fragment xml_xml, xml_id xml_char(30), xml_matched_element xml_char(8), xml_parent_child_pos xml_decimal(3,0), xml_parent_id xml_char(28), FieldInfos.SubtypeFieldInfo{}.DefaultValue xml_char(7), FieldInfos.SubtypeFieldInfo{}.DefaultValue.type xml_char(10), FieldInfos.SubtypeFieldInfo{}.DomainName xml_char(27), FieldInfos.SubtypeFieldInfo{}.FieldName xml_char(17), FieldInfos.SubtypeFieldInfo{}.type xml_char(22)
    -> ListExploder_3
ListExploder_3
    ATTR_ACCUM_MODE = Merge List Attributes
    ATTR_CONFLICT_RES = Use List Attribute Values
    INDEX_ATTR = _element_index
    LIST_ATTR = FieldInfos.SubtypeFieldInfo{}
    ELEMENTS -> AttributeKeeper_3
AttributeKeeper_3
    CREATE_BULK_MODE_FEATURES = NO
    KEEP_ATTRS = SubtypeName,DomainName,DefaultValue.type,FieldName,DefaultValue
    -> TestFilter
TestFilter
    DEFAULT_VALUE = <UNFILTERED>
    TEST_LIST = "BOOL_OP,OR,COMPOSITE_TEST,""""""1"""""",TEST_CLAUSE,TEST @Value(FieldName) = Subtype",Subtype
    Subtype -> Subtypes (writer XLSXW_1)
Subtypes (writer XLSXW_1)
    attributes: SubtypeName string(30), DefaultValue auto(20), DefaultValue.type auto(20), DomainName auto(20), FieldName auto(20)

Bookmark: Feature Classes, Relationship Classes and Feature Datasets
DataElement (reader XML_1)
    attributes: AliasName xml_char(26), AreaFieldName xml_char(11), BackwardPathLabel xml_char(14), CLSID xml_char(39), CanVersion xml_char(6), Cardinality xml_char(28), CatalogPath xml_char(45), Children.DataElement{}.AliasName xml_char(26), Children.DataElement{}.AreaFieldName xml_char(11), Children.DataElement{}.CLSID xml_char(39), Children.DataElement{}.CanVersion xml_char(6), Children.DataElement{}.CatalogPath xml_char(45), Children.DataElement{}.ConfigurationKeyword xml_char(1), Children.DataElement{}.ControllerMemberships xml_char(1), Children.DataElement{}.ControllerMemberships.type xml_char(33), Children.DataElement{}.CreatedAtFieldName xml_char(1), Children.DataElement{}.CreatorFieldName xml_char(1), Children.DataElement{}.DSID xml_decimal(3,0), Children.DataElement{}.DatasetType xml_char(24), Children.DataElement{}.EXTCLSID xml_char(39), Children.DataElement{}.EditedAtFieldName xml_char(1), Children.DataElement{}.EditorFieldName xml_char(1), Children.DataElement{}.EditorTrackingEnabled xml_char(6), Children.DataElement{}.ExtensionProperties.PropertyArray xml_char(1), Children.DataElement{}.ExtensionProperties.PropertyArray.type xml_char(32), Children.DataElement{}.ExtensionProperties.type xml_char(17), Children.DataElement{}.Extent.SpatialReference.HighPrecision xml_char(5), Children.DataElement{}.Extent.SpatialReference.LatestWKID xml_decimal(6,0), Children.DataElement{}.Extent.SpatialReference.MOrigin xml_decimal(2,0), Children.DataElement{}.Extent.SpatialReference.MScale xml_decimal(7,0),
      Children.DataElement{}.Extent.SpatialReference.MTolerance xml_decimal(31,15), Children.DataElement{}.Extent.SpatialReference.WKID xml_decimal(6,0), Children.DataElement{}.Extent.SpatialReference.WKT xml_char(450), Children.DataElement{}.Extent.SpatialReference.XOrigin xml_decimal(18,4), Children.DataElement{}.Extent.SpatialReference.XYScale xml_decimal(6,0), Children.DataElement{}.Extent.SpatialReference.XYTolerance xml_decimal(22,20), Children.DataElement{}.Extent.SpatialReference.YOrigin xml_decimal(18,4), Children.DataElement{}.Extent.SpatialReference.ZOrigin xml_decimal(2,0), Children.DataElement{}.Extent.SpatialReference.ZScale xml_decimal(7,0), Children.DataElement{}.Extent.SpatialReference.ZTolerance xml_decimal(31,15), Children.DataElement{}.Extent.SpatialReference.type xml_char(31), Children.DataElement{}.Extent.XMax xml_decimal(18,11), Children.DataElement{}.Extent.XMin xml_decimal(18,11), Children.DataElement{}.Extent.YMax xml_decimal(18,10), Children.DataElement{}.Extent.YMin xml_decimal(18,10), Children.DataElement{}.Extent.type xml_char(15), Children.DataElement{}.FeatureType xml_char(17), Children.DataElement{}.Fields.FieldArray.Field{}.AliasName xml_char(20), Children.DataElement{}.Fields.FieldArray.Field{}.DefaultValue xml_char(7), Children.DataElement{}.Fields.FieldArray.Field{}.DefaultValue.type xml_char(10), Children.DataElement{}.Fields.FieldArray.Field{}.Domain.CodedValues.CodedValue{}.Code xml_char(10), Children.DataElement{}.Fields.FieldArray.Field{}.Domain.CodedValues.CodedValue{}.Code.type xml_char(10), Children.DataElement{}.Fields.FieldArray.Field{}.Domain.CodedValues.CodedValue{}.Name xml_char(26), Children.DataElement{}.Fields.FieldArray.Field{}.Domain.CodedValues.CodedValue{}.type xml_char(16), Children.DataElement{}.Fields.FieldArray.Field{}.Domain.CodedValues.type xml_char(23), Children.DataElement{}.Fields.FieldArray.Field{}.Domain.Description xml_char(42), Children.DataElement{}.Fields.FieldArray.Field{}.Domain.DomainName xml_char(27), Children.DataElement{}.Fields.FieldArray.Field{}.Domain.FieldType xml_char(26), Children.DataElement{}.Fields.FieldArray.Field{}.Domain.MergePolicy xml_char(20), Children.DataElement{}.Fields.FieldArray.Field{}.Domain.Owner xml_char(1),
      Children.DataElement{}.Fields.FieldArray.Field{}.Domain.SplitPolicy xml_char(20), Children.DataElement{}.Fields.FieldArray.Field{}.Domain.type xml_char(22), Children.DataElement{}.Fields.FieldArray.Field{}.DomainFixed xml_char(5), Children.DataElement{}.Fields.FieldArray.Field{}.Editable xml_char(6), Children.DataElement{}.Fields.FieldArray.Field{}.GeometryDef.AvgNumPoints xml_decimal(2,0), Children.DataElement{}.Fields.FieldArray.Field{}.GeometryDef.GeometryType xml_char(21), Children.DataElement{}.Fields.FieldArray.Field{}.GeometryDef.GridSize0 xml_decimal(5,0), Children.DataElement{}.Fields.FieldArray.Field{}.GeometryDef.HasM xml_char(6), Children.DataElement{}.Fields.FieldArray.Field{}.GeometryDef.HasZ xml_char(6), Children.DataElement{}.Fields.FieldArray.Field{}.GeometryDef.SpatialReference.HighPrecision xml_char(5), Children.DataElement{}.Fields.FieldArray.Field{}.GeometryDef.SpatialReference.LatestWKID xml_decimal(6,0), Children.DataElement{}.Fields.FieldArray.Field{}.GeometryDef.SpatialReference.MOrigin xml_decimal(2,0), Children.DataElement{}.Fields.FieldArray.Field{}.GeometryDef.SpatialReference.MScale xml_decimal(7,0), Children.DataElement{}.Fields.FieldArray.Field{}.GeometryDef.SpatialReference.MTolerance xml_decimal(31,15), Children.DataElement{}.Fields.FieldArray.Field{}.GeometryDef.SpatialReference.WKID xml_decimal(6,0), Children.DataElement{}.Fields.FieldArray.Field{}.GeometryDef.SpatialReference.WKT xml_char(450), Children.DataElement{}.Fields.FieldArray.Field{}.GeometryDef.SpatialReference.XOrigin xml_decimal(18,4), Children.DataElement{}.Fields.FieldArray.Field{}.GeometryDef.SpatialReference.XYScale xml_decimal(6,0), Children.DataElement{}.Fields.FieldArray.Field{}.GeometryDef.SpatialReference.XYTolerance xml_decimal(22,20), Children.DataElement{}.Fields.FieldArray.Field{}.GeometryDef.SpatialReference.YOrigin xml_decimal(18,4), Children.DataElement{}.Fields.FieldArray.Field{}.GeometryDef.SpatialReference.ZOrigin xml_decimal(2,0), Children.DataElement{}.Fields.FieldArray.Field{}.GeometryDef.SpatialReference.ZScale xml_decimal(7,0), Children.DataElement{}.Fields.FieldArray.Field{}.GeometryDef.SpatialReference.ZTolerance xml_decimal(31,15), Children.DataElement{}.Fields.FieldArray.Field{}.GeometryDef.SpatialReference.type xml_char(31), Children.DataElement{}.Fields.FieldArray.Field{}.GeometryDef.type xml_char(17), Children.DataElement{}.Fields.FieldArray.Field{}.IsNullable xml_char(6), Children.DataElement{}.Fields.FieldArray.Field{}.Length xml_decimal(4,0), Children.DataElement{}.Fields.FieldArray.Field{}.ModelName xml_char(20), Children.DataElement{}.Fields.FieldArray.Field{}.Name xml_char(20), Children.DataElement{}.Fields.FieldArray.Field{}.Precision xml_decimal(2,0),
      Children.DataElement{}.Fields.FieldArray.Field{}.Required xml_char(5), Children.DataElement{}.Fields.FieldArray.Field{}.Scale xml_decimal(2,0), Children.DataElement{}.Fields.FieldArray.Field{}.Type xml_char(26), Children.DataElement{}.Fields.FieldArray.Field{}.type xml_char(11), Children.DataElement{}.Fields.FieldArray.type xml_char(18), Children.DataElement{}.Fields.type xml_char(12), Children.DataElement{}.GlobalIDFieldName xml_char(9), Children.DataElement{}.HasGlobalID xml_char(6), Children.DataElement{}.HasM xml_char(6), Children.DataElement{}.HasOID xml_char(6), Children.DataElement{}.HasSpatialIndex xml_char(5), Children.DataElement{}.HasZ xml_char(6), Children.DataElement{}.Indexes.IndexArray.Index{}.Fields.FieldArray.Field.Editable xml_char(6), Children.DataElement{}.Indexes.IndexArray.Index{}.Fields.FieldArray.Field.GeometryDef.AvgNumPoints xml_decimal(2,0), Children.DataElement{}.Indexes.IndexArray.Index{}.Fields.FieldArray.Field.GeometryDef.GeometryType xml_char(21), Children.DataElement{}.Indexes.IndexArray.Index{}.Fields.FieldArray.Field.GeometryDef.GridSize0 xml_decimal(5,0), Children.DataElement{}.Indexes.IndexArray.Index{}.Fields.FieldArray.Field.GeometryDef.HasM xml_char(6), Children.DataElement{}.Indexes.IndexArray.Index{}.Fields.FieldArray.Field.GeometryDef.HasZ xml_char(6), Children.DataElement{}.Indexes.IndexArray.Index{}.Fields.FieldArray.Field.GeometryDef.SpatialReference.HighPrecision xml_char(5), Children.DataElement{}.Indexes.IndexArray.Index{}.Fields.FieldArray.Field.GeometryDef.SpatialReference.LatestWKID xml_decimal(6,0), Children.DataElement{}.Indexes.IndexArray.Index{}.Fields.FieldArray.Field.GeometryDef.SpatialReference.MOrigin xml_decimal(2,0), Children.DataElement{}.Indexes.IndexArray.Index{}.Fields.FieldArray.Field.GeometryDef.SpatialReference.MScale xml_decimal(7,0), Children.DataElement{}.Indexes.IndexArray.Index{}.Fields.FieldArray.Field.GeometryDef.SpatialReference.MTolerance xml_decimal(31,15), Children.DataElement{}.Indexes.IndexArray.Index{}.Fields.FieldArray.Field.GeometryDef.SpatialReference.WKID xml_decimal(6,0), Children.DataElement{}.Indexes.IndexArray.Index{}.Fields.FieldArray.Field.GeometryDef.SpatialReference.WKT xml_char(450), Children.DataElement{}.Indexes.IndexArray.Index{}.Fields.FieldArray.Field.GeometryDef.SpatialReference.XOrigin xml_decimal(18,4), Children.DataElement{}.Indexes.IndexArray.Index{}.Fields.FieldArray.Field.GeometryDef.SpatialReference.XYScale xml_decimal(6,0), Children.DataElement{}.Indexes.IndexArray.Index{}.Fields.FieldArray.Field.GeometryDef.SpatialReference.XYTolerance xml_decimal(22,20), Children.DataElement{}.Indexes.IndexArray.Index{}.Fields.FieldArray.Field.GeometryDef.SpatialReference.YOrigin xml_decimal(18,4), Children.DataElement{}.Indexes.IndexArray.Index{}.Fields.FieldArray.Field.GeometryDef.SpatialReference.ZOrigin xml_decimal(2,0),
      Children.DataElement{}.Indexes.IndexArray.Index{}.Fields.FieldArray.Field.GeometryDef.SpatialReference.ZScale xml_decimal(7,0), Children.DataElement{}.Indexes.IndexArray.Index{}.Fields.FieldArray.Field.GeometryDef.SpatialReference.ZTolerance xml_decimal(31,15), Children.DataElement{}.Indexes.IndexArray.Index{}.Fields.FieldArray.Field.GeometryDef.SpatialReference.type xml_char(31), Children.DataElement{}.Indexes.IndexArray.Index{}.Fields.FieldArray.Field.GeometryDef.type xml_char(17), Children.DataElement{}.Indexes.IndexArray.Index{}.Fields.FieldArray.Field.IsNullable xml_char(6), Children.DataElement{}.Indexes.IndexArray.Index{}.Fields.FieldArray.Field.Length xml_decimal(3,0), Children.DataElement{}.Indexes.IndexArray.Index{}.Fields.FieldArray.Field.Name xml_char(18), Children.DataElement{}.Indexes.IndexArray.Index{}.Fields.FieldArray.Field.Precision xml_decimal(2,0), Children.DataElement{}.Indexes.IndexArray.Index{}.Fields.FieldArray.Field.Required xml_char(5), Children.DataElement{}.Indexes.IndexArray.Index{}.Fields.FieldArray.Field.Scale xml_decimal(2,0), Children.DataElement{}.Indexes.IndexArray.Index{}.Fields.FieldArray.Field.Type xml_char(26), Children.DataElement{}.Indexes.IndexArray.Index{}.Fields.FieldArray.Field.type xml_char(11), Children.DataElement{}.Indexes.IndexArray.Index{}.Fields.FieldArray.type xml_char(18), Children.DataElement{}.Indexes.IndexArray.Index{}.Fields.type xml_char(12), Children.DataElement{}.Indexes.IndexArray.Index{}.IsAscending xml_char(5), Children.DataElement{}.Indexes.IndexArray.Index{}.IsUnique xml_char(6), Children.DataElement{}.Indexes.IndexArray.Index{}.Name xml_char(21), Children.DataElement{}.Indexes.IndexArray.Index{}.type xml_char(11), Children.DataElement{}.Indexes.IndexArray.type xml_char(18), Children.DataElement{}.Indexes.type xml_char(13), Children.DataElement{}.IsTimeInUTC xml_char(5), Children.DataElement{}.LengthFieldName xml_char(13), Children.DataElement{}.ModelName xml_char(1), Children.DataElement{}.Name xml_char(19), Children.DataElement{}.OIDFieldName xml_char(9), Children.DataElement{}.RasterFieldName xml_char(1), Children.DataElement{}.RelationshipClassNames xml_char(1), Children.DataElement{}.RelationshipClassNames.Name xml_char(11), Children.DataElement{}.RelationshipClassNames.type xml_char(11), Children.DataElement{}.ShapeFieldName xml_char(6),
      Children.DataElement{}.ShapeType xml_char(21), Children.DataElement{}.SpatialReference.HighPrecision xml_char(5), Children.DataElement{}.SpatialReference.LatestWKID xml_decimal(6,0), Children.DataElement{}.SpatialReference.MOrigin xml_decimal(2,0), Children.DataElement{}.SpatialReference.MScale xml_decimal(7,0), Children.DataElement{}.SpatialReference.MTolerance xml_decimal(31,15), Children.DataElement{}.SpatialReference.WKID xml_decimal(6,0), Children.DataElement{}.SpatialReference.WKT xml_char(450), Children.DataElement{}.SpatialReference.XOrigin xml_decimal(18,4), Children.DataElement{}.SpatialReference.XYScale xml_decimal(6,0), Children.DataElement{}.SpatialReference.XYTolerance xml_decimal(22,20), Children.DataElement{}.SpatialReference.YOrigin xml_decimal(18,4), Children.DataElement{}.SpatialReference.ZOrigin xml_decimal(2,0), Children.DataElement{}.SpatialReference.ZScale xml_decimal(7,0), Children.DataElement{}.SpatialReference.ZTolerance xml_decimal(31,15), Children.DataElement{}.SpatialReference.type xml_char(31), Children.DataElement{}.Versioned xml_char(6), Children.DataElement{}.type xml_char(25), Children.type xml_char(24), ClassKey xml_char(25), ConfigurationKeyword xml_char(1), ControllerMemberships xml_char(1), ControllerMemberships.type xml_char(33), CreatedAtFieldName xml_char(1), CreatorFieldName xml_char(1), DSID xml_decimal(3,0), DataElement.type xml_char(25), DatasetDefinitions.type xml_char(24), DatasetType xml_char(24), DestinationClassNames.Name xml_char(19),
      DestinationClassNames.type xml_char(11), EXTCLSID xml_char(39), EditedAtFieldName xml_char(1), EditorFieldName xml_char(1), EditorTrackingEnabled xml_char(6), ExtensionProperties.PropertyArray xml_char(1), ExtensionProperties.PropertyArray.type xml_char(32), ExtensionProperties.type xml_char(17), Extent.SpatialReference.HighPrecision xml_char(5), Extent.SpatialReference.LatestWKID xml_decimal(6,0), Extent.SpatialReference.MOrigin xml_decimal(8,0), Extent.SpatialReference.MScale xml_decimal(7,0), Extent.SpatialReference.MTolerance xml_decimal(31,15), Extent.SpatialReference.WKID xml_decimal(6,0), Extent.SpatialReference.WKT xml_char(450), Extent.SpatialReference.XOrigin xml_decimal(18,4), Extent.SpatialReference.XYScale xml_decimal(6,0), Extent.SpatialReference.XYTolerance xml_decimal(22,20), Extent.SpatialReference.YOrigin xml_decimal(18,4), Extent.SpatialReference.ZOrigin xml_decimal(8,0), Extent.SpatialReference.ZScale xml_decimal(7,0), Extent.SpatialReference.ZTolerance xml_decimal(31,15), Extent.SpatialReference.type xml_char(31), Extent.XMax xml_decimal(18,11), Extent.XMin xml_decimal(18,11), Extent.YMax xml_decimal(18,10), Extent.YMin xml_decimal(18,10), Extent.type xml_char(15), FeatureType xml_char(17), Fields.FieldArray xml_char(1),
      Fields.FieldArray.Field{}.AliasName xml_char(21), Fields.FieldArray.Field{}.DefaultValue xml_char(7), Fields.FieldArray.Field{}.DefaultValue.type xml_char(10), Fields.FieldArray.Field{}.Domain.CodedValues.CodedValue{}.Code xml_char(10), Fields.FieldArray.Field{}.Domain.CodedValues.CodedValue{}.Code.type xml_char(10), Fields.FieldArray.Field{}.Domain.CodedValues.CodedValue{}.Name xml_char(26), Fields.FieldArray.Field{}.Domain.CodedValues.CodedValue{}.type xml_char(16), Fields.FieldArray.Field{}.Domain.CodedValues.type xml_char(23), Fields.FieldArray.Field{}.Domain.Description xml_char(42), Fields.FieldArray.Field{}.Domain.DomainName xml_char(27), Fields.FieldArray.Field{}.Domain.FieldType xml_char(26), Fields.FieldArray.Field{}.Domain.MergePolicy xml_char(20), Fields.FieldArray.Field{}.Domain.Owner xml_char(1), Fields.FieldArray.Field{}.Domain.SplitPolicy xml_char(20), Fields.FieldArray.Field{}.Domain.type xml_char(22), Fields.FieldArray.Field{}.DomainFixed xml_char(5), Fields.FieldArray.Field{}.Editable xml_char(6), Fields.FieldArray.Field{}.GeometryDef.AvgNumPoints xml_decimal(2,0), Fields.FieldArray.Field{}.GeometryDef.GeometryType xml_char(21), Fields.FieldArray.Field{}.GeometryDef.GridSize0 xml_decimal(6,0), Fields.FieldArray.Field{}.GeometryDef.HasM xml_char(6), Fields.FieldArray.Field{}.GeometryDef.HasZ xml_char(6), Fields.FieldArray.Field{}.GeometryDef.SpatialReference.HighPrecision xml_char(5), Fields.FieldArray.Field{}.GeometryDef.SpatialReference.LatestWKID xml_decimal(6,0), Fields.FieldArray.Field{}.GeometryDef.SpatialReference.MOrigin xml_decimal(8,0), Fields.FieldArray.Field{}.GeometryDef.SpatialReference.MScale xml_decimal(7,0), Fields.FieldArray.Field{}.GeometryDef.SpatialReference.MTolerance xml_decimal(31,15), Fields.FieldArray.Field{}.GeometryDef.SpatialReference.WKID xml_decimal(6,0), Fields.FieldArray.Field{}.GeometryDef.SpatialReference.WKT xml_char(450), Fields.FieldArray.Field{}.GeometryDef.SpatialReference.XOrigin xml_decimal(18,4),
      Fields.FieldArray.Field{}.GeometryDef.SpatialReference.XYScale xml_decimal(6,0), Fields.FieldArray.Field{}.GeometryDef.SpatialReference.XYTolerance xml_decimal(22,20), Fields.FieldArray.Field{}.GeometryDef.SpatialReference.YOrigin xml_decimal(18,4), Fields.FieldArray.Field{}.GeometryDef.SpatialReference.ZOrigin xml_decimal(8,0), Fields.FieldArray.Field{}.GeometryDef.SpatialReference.ZScale xml_decimal(7,0), Fields.FieldArray.Field{}.GeometryDef.SpatialReference.ZTolerance xml_decimal(31,15), Fields.FieldArray.Field{}.GeometryDef.SpatialReference.type xml_char(31), Fields.FieldArray.Field{}.GeometryDef.type xml_char(17), Fields.FieldArray.Field{}.IsNullable xml_char(6), Fields.FieldArray.Field{}.Length xml_decimal(4,0), Fields.FieldArray.Field{}.ModelName xml_char(21), Fields.FieldArray.Field{}.Name xml_char(21), Fields.FieldArray.Field{}.Precision xml_decimal(2,0), Fields.FieldArray.Field{}.Required xml_char(5), Fields.FieldArray.Field{}.Scale xml_decimal(2,0), Fields.FieldArray.Field{}.Type xml_char(26), Fields.FieldArray.Field{}.type xml_char(11), Fields.FieldArray.type xml_char(18), Fields.type xml_char(12), ForwardPathLabel xml_char(19), GlobalIDFieldName xml_char(9), HasGlobalID xml_char(6), HasM xml_char(6), HasOID xml_char(6), HasSpatialIndex xml_char(5), HasZ xml_char(6), Indexes.IndexArray xml_char(1), Indexes.IndexArray.Index{}.Fields.FieldArray.Field.AliasName xml_char(9), Indexes.IndexArray.Index{}.Fields.FieldArray.Field.Editable xml_char(6), Indexes.IndexArray.Index{}.Fields.FieldArray.Field.GeometryDef.AvgNumPoints xml_decimal(2,0),
      Indexes.IndexArray.Index{}.Fields.FieldArray.Field.GeometryDef.GeometryType xml_char(21), Indexes.IndexArray.Index{}.Fields.FieldArray.Field.GeometryDef.GridSize0 xml_decimal(6,0), Indexes.IndexArray.Index{}.Fields.FieldArray.Field.GeometryDef.HasM xml_char(6), Indexes.IndexArray.Index{}.Fields.FieldArray.Field.GeometryDef.HasZ xml_char(6), Indexes.IndexArray.Index{}.Fields.FieldArray.Field.GeometryDef.SpatialReference.HighPrecision xml_char(5), Indexes.IndexArray.Index{}.Fields.FieldArray.Field.GeometryDef.SpatialReference.LatestWKID xml_decimal(6,0), Indexes.IndexArray.Index{}.Fields.FieldArray.Field.GeometryDef.SpatialReference.MOrigin xml_decimal(8,0), Indexes.IndexArray.Index{}.Fields.FieldArray.Field.GeometryDef.SpatialReference.MScale xml_decimal(7,0), Indexes.IndexArray.Index{}.Fields.FieldArray.Field.GeometryDef.SpatialReference.MTolerance xml_decimal(31,15), Indexes.IndexArray.Index{}.Fields.FieldArray.Field.GeometryDef.SpatialReference.WKID xml_decimal(6,0), Indexes.IndexArray.Index{}.Fields.FieldArray.Field.GeometryDef.SpatialReference.WKT xml_char(450), Indexes.IndexArray.Index{}.Fields.FieldArray.Field.GeometryDef.SpatialReference.XOrigin xml_decimal(18,4), Indexes.IndexArray.Index{}.Fields.FieldArray.Field.GeometryDef.SpatialReference.XYScale xml_decimal(6,0), Indexes.IndexArray.Index{}.Fields.FieldArray.Field.GeometryDef.SpatialReference.XYTolerance xml_decimal(22,20), Indexes.IndexArray.Index{}.Fields.FieldArray.Field.GeometryDef.SpatialReference.YOrigin xml_decimal(18,4), Indexes.IndexArray.Index{}.Fields.FieldArray.Field.GeometryDef.SpatialReference.ZOrigin xml_decimal(8,0), Indexes.IndexArray.Index{}.Fields.FieldArray.Field.GeometryDef.SpatialReference.ZScale xml_decimal(7,0), Indexes.IndexArray.Index{}.Fields.FieldArray.Field.GeometryDef.SpatialReference.ZTolerance xml_decimal(31,15), Indexes.IndexArray.Index{}.Fields.FieldArray.Field.GeometryDef.SpatialReference.type xml_char(31), Indexes.IndexArray.Index{}.Fields.FieldArray.Field.GeometryDef.type xml_char(17), Indexes.IndexArray.Index{}.Fields.FieldArray.Field.IsNullable xml_char(6), Indexes.IndexArray.Index{}.Fields.FieldArray.Field.Length xml_decimal(3,0), Indexes.IndexArray.Index{}.Fields.FieldArray.Field.ModelName xml_char(9), Indexes.IndexArray.Index{}.Fields.FieldArray.Field.Name xml_char(18), Indexes.IndexArray.Index{}.Fields.FieldArray.Field.Precision xml_decimal(2,0), Indexes.IndexArray.Index{}.Fields.FieldArray.Field.Required xml_char(5), Indexes.IndexArray.Index{}.Fields.FieldArray.Field.Scale xml_decimal(2,0), Indexes.IndexArray.Index{}.Fields.FieldArray.Field.Type xml_char(26), Indexes.IndexArray.Index{}.Fields.FieldArray.Field.type xml_char(11), Indexes.IndexArray.Index{}.Fields.FieldArray.type xml_char(18),
      Indexes.IndexArray.Index{}.Fields.type xml_char(12), Indexes.IndexArray.Index{}.IsAscending xml_char(5), Indexes.IndexArray.Index{}.IsUnique xml_char(6), Indexes.IndexArray.Index{}.Name xml_char(21), Indexes.IndexArray.Index{}.type xml_char(11), Indexes.IndexArray.type xml_char(18), Indexes.type xml_char(13), IsAttachmentRelationship xml_char(6), IsAttributed xml_char(6), IsComposite xml_char(5), IsReflexive xml_char(6), IsTimeInUTC xml_char(5), KeyType xml_char(21), LengthFieldName xml_char(13), Metadata.XmlDoc xml_char(521), Metadata.type xml_char(20), MetadataRetrieved xml_char(5), ModelName xml_char(1), Name xml_char(19), Notification xml_char(27), OIDFieldName xml_char(9), OriginClassKeys.RelationshipClassKey{}.ClassKeyName xml_char(1), OriginClassKeys.RelationshipClassKey{}.KeyRole xml_char(28), OriginClassKeys.RelationshipClassKey{}.ObjectKeyName xml_char(10), OriginClassKeys.RelationshipClassKey{}.type xml_char(26), OriginClassKeys.type xml_char(33), OriginClassNames.Name xml_char(14), OriginClassNames.type xml_char(11), RasterFieldName xml_char(1), RelationshipClassNames xml_char(1),
      RelationshipClassNames.Name xml_char(11), RelationshipClassNames.type xml_char(11), RelationshipRules xml_char(1), RelationshipRules.type xml_char(29), ShapeFieldName xml_char(6), ShapeType xml_char(21), SpatialReference.HighPrecision xml_char(5), SpatialReference.LatestWKID xml_decimal(6,0), SpatialReference.MOrigin xml_decimal(8,0), SpatialReference.MScale xml_decimal(7,0), SpatialReference.MTolerance xml_decimal(31,15), SpatialReference.WKID xml_decimal(6,0), SpatialReference.WKT xml_char(450), SpatialReference.XOrigin xml_decimal(18,4), SpatialReference.XYScale xml_decimal(6,0), SpatialReference.XYTolerance xml_decimal(22,20), SpatialReference.YOrigin xml_decimal(18,4), SpatialReference.ZOrigin xml_decimal(8,0), SpatialReference.ZScale xml_decimal(7,0), SpatialReference.ZTolerance xml_decimal(31,15), SpatialReference.type xml_char(31), Versioned xml_char(6), xml_fragment xml_xml, xml_id xml_char(28), xml_matched_element xml_char(12), xml_parent_child_pos xml_decimal(3,0), xml_parent_id xml_char(23), ChangeTracked xml_char(6), Children.DataElement{}.BackwardPathLabel xml_char(14), Children.DataElement{}.Cardinality xml_char(28),
      Children.DataElement{}.ChangeTracked xml_char(6), Children.DataElement{}.ChildrenExpanded xml_char(6), Children.DataElement{}.ClassKey xml_char(25), Children.DataElement{}.DefaultSubtypeCode xml_decimal(2,0), Children.DataElement{}.DestinationClassNames.Name xml_char(19), Children.DataElement{}.DestinationClassNames.type xml_char(11), Children.DataElement{}.ExtensionProperties.PropertyArray.PropertySetProperty{}.Key xml_char(21), Children.DataElement{}.ExtensionProperties.PropertyArray.PropertySetProperty{}.Value xml_char(14), Children.DataElement{}.ExtensionProperties.PropertyArray.PropertySetProperty{}.Value.Bytes xml_char(11049), Children.DataElement{}.ExtensionProperties.PropertyArray.PropertySetProperty{}.Value.type xml_char(24), Children.DataElement{}.ExtensionProperties.PropertyArray.PropertySetProperty{}.type xml_char(25), Children.DataElement{}.Fields.FieldArray xml_char(1), Children.DataElement{}.ForwardPathLabel xml_char(19), Children.DataElement{}.Indexes.IndexArray xml_char(1), Children.DataElement{}.Indexes.IndexArray.Index{}.Fields.FieldArray.Field.DefaultValue xml_decimal(2,0), Children.DataElement{}.Indexes.IndexArray.Index{}.Fields.FieldArray.Field.DefaultValue.type xml_char(9), Children.DataElement{}.IsAttachmentRelationship xml_char(6), Children.DataElement{}.IsAttributed xml_char(6), Children.DataElement{}.IsComposite xml_char(5), Children.DataElement{}.IsReflexive xml_char(6), Children.DataElement{}.KeyType xml_char(21), Children.DataElement{}.Notification xml_char(27), Children.DataElement{}.OriginClassKeys.RelationshipClassKey{}.ClassKeyName xml_char(1), Children.DataElement{}.OriginClassKeys.RelationshipClassKey{}.KeyRole xml_char(28), Children.DataElement{}.OriginClassKeys.RelationshipClassKey{}.ObjectKeyName xml_char(10), Children.DataElement{}.OriginClassKeys.RelationshipClassKey{}.type xml_char(26), Children.DataElement{}.OriginClassKeys.type xml_char(33), Children.DataElement{}.OriginClassNames.Name xml_char(14), Children.DataElement{}.OriginClassNames.type xml_char(11), Children.DataElement{}.RelationshipRules xml_char(1),
      Children.DataElement{}.RelationshipRules.type xml_char(29), Children.DataElement{}.SubtypeFieldName xml_char(8), Children.DataElement{}.Subtypes.Subtype{}.FieldInfos.SubtypeFieldInfo{}.DefaultValue xml_char(7), Children.DataElement{}.Subtypes.Subtype{}.FieldInfos.SubtypeFieldInfo{}.DefaultValue.type xml_char(10), Children.DataElement{}.Subtypes.Subtype{}.FieldInfos.SubtypeFieldInfo{}.DomainName xml_char(27), Children.DataElement{}.Subtypes.Subtype{}.FieldInfos.SubtypeFieldInfo{}.FieldName xml_char(17), Children.DataElement{}.Subtypes.Subtype{}.FieldInfos.SubtypeFieldInfo{}.type xml_char(22), Children.DataElement{}.Subtypes.Subtype{}.FieldInfos.type xml_char(29), Children.DataElement{}.Subtypes.Subtype{}.SubtypeCode xml_decimal(3,0), Children.DataElement{}.Subtypes.Subtype{}.SubtypeName xml_char(24), Children.DataElement{}.Subtypes.Subtype{}.type xml_char(13), Children.DataElement{}.Subtypes.type xml_char(20), ChildrenExpanded xml_char(6), DefaultSubtypeCode xml_decimal(2,0), ExtensionProperties.PropertyArray.PropertySetProperty{}.Key xml_char(21), ExtensionProperties.PropertyArray.PropertySetProperty{}.Value xml_char(14), ExtensionProperties.PropertyArray.PropertySetProperty{}.Value.Bytes xml_char(11049), ExtensionProperties.PropertyArray.PropertySetProperty{}.Value.type xml_char(24), ExtensionProperties.PropertyArray.PropertySetProperty{}.type xml_char(25), Indexes.IndexArray.Index{}.Fields.FieldArray.Field.DefaultValue xml_decimal(2,0), Indexes.IndexArray.Index{}.Fields.FieldArray.Field.DefaultValue.type xml_char(9), SubtypeFieldName xml_char(8), Subtypes.Subtype{}.FieldInfos.SubtypeFieldInfo{}.DefaultValue xml_char(7), Subtypes.Subtype{}.FieldInfos.SubtypeFieldInfo{}.DefaultValue.type xml_char(10), Subtypes.Subtype{}.FieldInfos.SubtypeFieldInfo{}.DomainName xml_char(27), Subtypes.Subtype{}.FieldInfos.SubtypeFieldInfo{}.FieldName xml_char(17), Subtypes.Subtype{}.FieldInfos.SubtypeFieldInfo{}.type xml_char(22), Subtypes.Subtype{}.FieldInfos.type xml_char(29), Subtypes.Subtype{}.SubtypeCode xml_decimal(3,0), Subtypes.Subtype{}.SubtypeName xml_char(24),
      Subtypes.Subtype{}.type xml_char(13), Subtypes.type xml_char(20)
    -> AttributeKeeper
    -> ListExploder_4
Note: Each record = 1 table or feature dataset / with its table name, fields, properties and coded domains if any
AttributeKeeper
    CREATE_BULK_MODE_FEATURES = No
    KEEP_ATTRS = MetadataRetrieved,Extent.SpatialReference.WKID,Extent.SpatialReference.ZScale,Extent.YMin,DatasetType,Extent.SpatialReference.XYScale,Extent.XMax,Name,Extent.SpatialReference.ZTolerance,Extent.XMin,Extent.SpatialReference.WKT,Metadata.type,Extent.YMax,AliasName,Extent.SpatialReference.type,Extent.SpatialReference.XOrigin,Extent.SpatialReference.YOrigin,Extent.type,Extent.SpatialReference.XYTolerance,Extent.SpatialReference.LatestWKID,Extent.SpatialReference.ZOrigin,Metadata.XmlDoc
    -> FeatureClasses&Metadata (writer XLSXW_1)
FeatureClasses&Metadata (writer XLSXW_1)
    attributes: AliasName string(26), DatasetType string(24), Extent.SpatialReference.LatestWKID number(6), Extent.SpatialReference.WKID number(6), Extent.SpatialReference.WKT string(450), Extent.SpatialReference.XOrigin number(18), Extent.SpatialReference.XYScale number(6), Extent.SpatialReference.XYTolerance number(22), Extent.SpatialReference.YOrigin number(18), Extent.SpatialReference.ZOrigin number(8), Extent.SpatialReference.ZScale number(7), Extent.SpatialReference.ZTolerance number(31), Extent.SpatialReference.type string(31), Extent.XMax number(18), Extent.XMin number(18), Extent.YMax number(18), Extent.YMin number(18), Extent.type string(15), Metadata.XmlDoc string(521), Metadata.type string(20), MetadataRetrieved string(5), Name string(19)

Bookmark: Fields, their properties and parent table names
ListExploder_4
    ATTR_ACCUM_MODE = Prefix List Attributes
    INCOMING_PREFIX = fields_
    INDEX_ATTR = _element_index
    LIST_ATTR = Fields.FieldArray.Field{}
    ELEMENTS -> AttributeKeeper_4
    <REJECTED> -> Junction
AttributeKeeper_4
    CREATE_BULK_MODE_FEATURES = No
    KEEP_ATTRS = Name,fields_Precision,AliasName,fields_Type,fields_Name,fields_Domain.DomainName
    -> Fields (writer XLSXW_1)
Note: Each record = 1 field / with its table name, properties / and coded domains if any
Fields (writer XLSXW_1)
    attributes: FeatureClass string(19), FeatureClass Alias string(26), AttributeName auto(20), Domain auto(20), DataType auto(20)
Junction

Bookmark: Documentation
Note: Geodatabase XML Schema Reader / Version: 1.0 / Version required: FME 2013 or above / Last modified: Feb. 14, 2013 / By: Dean at Safe / FME 2019.2 2020-03-19 / Updated by: MarkS / Changes: / removed schema reader / switched to Excel output / FME 2021.2 2021-12-01 / Updated by: Mark Stoakes / Changes: / reorder sheets / improve column names / Purpose: Read all possible schema elements / from an ESRI Geodatabase XML Workspace Dataset / Uses the Schema reader to get basic table and / field information. / Uses the XML reader with feature paths to get / detailed schema information at the / dataset, feature class and field levels. / Also retrieves all dataset metadata.
